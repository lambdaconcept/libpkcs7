Simplified-PKCS7 DEFINITIONS EXPLICIT TAGS ::= BEGIN 

IMPORTS
	Certificate FROM PKIX1Explicit88 { iso(1) identified-organization(3)
 dod(6) internet(1) security(5) mechanisms(5) pkix(7)
 id-mod(0) id-pkix1-explicit(18) };


SignedData ::= SEQUENCE {
    contentType OBJECT IDENTIFIER,
    content [0] SEQUENCE {
        version INTEGER,
        digestAlgorithms    DigestAlgorithmIdentifiers,
        contentInfo SEQUENCE {
            contentType OBJECT IDENTIFIER,
            contentData [0] OCTET STRING
        },
        certificates [0] Certificate,
        crls [1] ANY OPTIONAL,
        signerInfos SignerInfos
    }
}

Ecdsa-Sig-Value  ::=  SEQUENCE  {
           r     INTEGER,
           s     INTEGER  }

Sha256-Digest-Value ::= SET OF OCTET STRING

ReceiptAttribute ::= SEQUENCE {
    type    INTEGER,
    version INTEGER,
    value   OCTET STRING
}
 
ReceiptAttributes ::= SET OF ReceiptAttribute

   SignerInfo ::= SEQUENCE {
     version INTEGER,
     issuerAndSerialNumber IssuerAndSerialNumber,
     digestAlgorithm DigestAlgorithmIdentifier,
     authenticatedAttributes
       [0] IMPLICIT Attributes OPTIONAL,
     digestEncryptionAlgorithm
       DigestEncryptionAlgorithmIdentifier,
     encryptedDigest EncryptedDigest,
     unauthenticatedAttributes
       [1] IMPLICIT Attributes OPTIONAL }

   EncryptedDigest ::= OCTET STRING

   SignerInfos ::= SET OF SignerInfo

DigestAlgorithmIdentifiers ::= SET OF DigestAlgorithmIdentifier

DigestAlgorithmIdentifier ::= AlgorithmIdentifier

DigestEncryptionAlgorithmIdentifier ::= DigestAlgorithmIdentifier

Attributes ::= SET OF AttributeTypeAndValue

AlgorithmIdentifier ::= SEQUENCE {
      algorithm       OBJECT IDENTIFIER,
      parameters      ANY OPTIONAL
}

IssuerAndSerialNumber ::= SEQUENCE {
     issuer Name,
     serialNumber INTEGER }

ReceiptString ::= CHOICE {
    utf8String UTF8String,
    ia5String IA5String }

END
